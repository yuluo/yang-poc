module idirect-enum {
	namespace "http://yang.idirect.net/idirect-enum";
	prefix idirectenum;
	
	revision 2019-02-26 {
	  description "prove of concept";
	}
	
	typedef network-version {
		type enumeration {
			enum 1.0.0.0;
			enum 1.2.0.0;
		}
	}
	
	typedef beamtype {
		type enumeration {
			enum Circular;
			enum Non-Circular;
		}
	}
	
	typedef emodulationtype {
		type enumeration {
			enum BPSK;
			enum QPSK;
			enum 8PSK;
			enum 16PSK;
			enum CCM;
			enum ACM;
			enum SSB;
			enum Adaptive;
		}
	}
	
	typedef emodcodtype {
		type enumeration {
			enum QPSK-1/4;
			enum QPSK-1/3;
			enum QPSK-2/5;
			enum QPSK-1/2;
			enum QPSK-3/5;
			enum QPSK-2/3;
			enum QPSK-3/4;
			enum QPSK-4/5;
			enum QPSK-5/6;
			enum QPSK-8/9;
            enum QPSK-9/10;
            enum 8PSK-3/5;
            enum 8PSK-2/3;
            enum 8PSK-3/4;
            enum 8PSK-5/6;
            enum 8PSK-8/9;
            enum 8PSK-9/10;
            enum 16APSK-2/3;
            enum 16APSK-3/4;
            enum 16APSK-4/5;
            enum 16APSK-5/6;
            enum 16APSK-8/9;
            enum 16APSK-9/10;
            enum 32APSK-3/4;
            enum 32APSK-4/5;
            enum 32APSK-5/6;
            enum 32APSK-8/9;
            enum 32APSK-9/10;
        }
	}
}
